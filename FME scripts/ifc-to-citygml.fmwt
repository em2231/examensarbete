FME workspace ifc-to-citygml.fmwt
Title: MULTI to MULTI

Parameters:
- DestDataset_CITYGML =
- DestDataset_CITYGML_3 =
- FEATURE_TYPES =
- OutputFolder =
- SourceDataset_IFC =
- SourceDataset_IFC_3 =

Readers:
- IFC_1: IFC from $(SourceDataset_IFC) in SWEREF-99-13-30
- IFC_2: IFC from $(SourceDataset_IFC_3) in SWEREF-99-13-30

Writers:
- CITYGML_2: CITYGML to $(DestDataset_CITYGML_3)
- CITYGML_1: CITYGML to $(DestDataset_CITYGML)

Note: Workflow source: / Colucci, E., Ruvo, V.D., Lingua, A., Matrone, F. & Rizzo, G., (2020), HBIM-GIS Integration: From IFC to CityGML Standard for Damaged Cultural Heritage in a Multiscale 3D GIS, Appl. Sci., 2020, 10(4), 1356; https://doi.org/10.3390/app10041356

Bookmark: IFC - Spacemaker
IfcBuildingStorey (reader IFC_1)
    attributes: GlobalId char(22), Name string, Description string, ObjectType string, LongName string, CompositionType enumeration, Elevation real, ifc_type_object_id string
IfcProject (reader IFC_1)
    attributes: GlobalId char(22), Name string, Description string, ObjectType string, LongName string, Phase string, ifc_type_object_id string
IfcSite (reader IFC_1)
    attributes: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
IfcTypeObject (reader IFC_1)
    attributes: ifc_type_name string, GlobalId char(22), Name string, Description string, ApplicableOccurrence string, Tag string, ElementType string, PredefinedType string
PropertySetDefinition (reader IFC_1)
    attributes: ifc_properties{}.data_type string, ifc_properties{}.name string, ifc_properties{}.property_type string, ifc_property_set_name string
QuantitySetDefinition (reader IFC_1)
    attributes: ifc_quantities{}.name string, ifc_quantities{}.type string, ifc_quantity_set_name string

Bookmark: Create parent/child lookup
IfcBuilding (reader IFC_2)
    attributes: GlobalId char(22), Name string, Description string, ObjectType string, LongName string, CompositionType string, ElevationOfRefHeight real, ElevationOfTerrain real, BuildingAddress.Purpose enumeration, BuildingAddress.Description string, BuildingAddress.UserDefinedPurpose string, BuildingAddress.InternalLocation string, BuildingAddress.AddressLines string, BuildingAddress.PostalBox string, BuildingAddress.Town string, BuildingAddress.Region string, BuildingAddress.PostalCode string, BuildingAddress.Country string, ApplicableOccurrence string, ElementType string, Elevation real, LandTitleNumber string, Phase string, PredefinedType string, RefElevation real, RefLatitude real, RefLongitude real, SiteAddress.AddressLines string, SiteAddress.Country string, SiteAddress.Description string,
      SiteAddress.InternalLocation string, SiteAddress.PostalBox string, SiteAddress.PostalCode string, SiteAddress.Purpose enumeration, SiteAddress.Region string, SiteAddress.Town string, SiteAddress.UserDefinedPurpose string, Tag string, ifc_type_name string, ifc_type_object_id string
    -> BinaryEncoder
BinaryEncoder
    ATTR_TO_ENCODE = ifc_unique_id
    DEST_ATTR = _unique_id
    ENCODING_TYPE = HEX
    -> BinaryEncoder_2
BinaryEncoder_2
    ATTR_TO_ENCODE = ifc_parent_unique_id
    DEST_ATTR = _parent_id
    ENCODING_TYPE = HEX
    -> VariableSetter
VariableSetter
    SCOPE = Global
    VALUE = @Value(_parent_id)
    VARNAME = p@Value(_unique_id)
    -> VariableSetter_2
VariableSetter_2
    SCOPE = Global
    VALUE = @Value(fme_feature_type)
    VARNAME = t@Value(_unique_id)

Bookmark: Building
IfcBuilding (reader IFC_1)
    attributes: GlobalId char(22), Name string, Description string, ObjectType string, LongName string, CompositionType string, ElevationOfRefHeight real, ElevationOfTerrain real, BuildingAddress.Purpose enumeration, BuildingAddress.Description string, BuildingAddress.UserDefinedPurpose string, BuildingAddress.InternalLocation string, BuildingAddress.AddressLines string, BuildingAddress.PostalBox string, BuildingAddress.Town string, BuildingAddress.Region string, BuildingAddress.PostalCode string, BuildingAddress.Country string, ifc_type_object_id string
    -> GeometryRemover
Note: Remove Geometry
GeometryRemover
    -> AttributeRenamer_12
Note: Set gml_id
AttributeRenamer_12
    ATTR_TABLE = RENAME_SET_DEFAULT ifc_unique_id > gml_id
    -> Building (writer CITYGML_1)
Building (writer CITYGML_1)

Bookmark: Buildingart
IfcBuildingElementProxy (reader IFC_1)
    attributes: GlobalId char(22), Name string, Description string, ObjectType string, Tag string, CompositionType enumeration, ifc_type_object_id string
    -> ConvertGeometry_13
Note: Convert Geometry to / simple surface
ConvertGeometry_13
    IFC_UNIQUE_ID = @Value(ifc_unique_id)
    -> AttributeRenamer_11
Note: Set gml id
AttributeRenamer_11
    ATTR_TABLE:
      RENAME_SET_DEFAULT ifc_parent_unique_id > gml_parent_id
      RENAME_SET_DEFAULT ifc_unique_id > gml_id
    -> GetGrandParentID_11
Note: Set parent id
GetGrandParentID_11
    ATTR_TO_ENCODE = gml_parent_id
    DEST_ATTR = gml_parent_id
    -> CityGMLGeometrySetter
Note: Set LOD and role
CityGMLGeometrySetter
    GEOM = lod1MultiSurface
    ROLE = cityObjectMember
    -> BuildingPart (writer CITYGML_2)
BuildingPart (writer CITYGML_2)

FME custom transformer ConvertGeometry

Parameters:
- IFC_UNIQUE_ID =

Bookmark: 'ConvertGeometry
Input (input)
    -> GeometryPartExtractor_3
GeometryPartExtractor_3
    GQUERY:
      for $geom in //geometry
      where $geom/@fme_geometry_name = 'Body'
      return number($geom/@fme_id)
    EXTRACTED -> GeometryCoercer_3
GeometryCoercer_3
    GQUERY:
      for $geom in //geometry
      where $geom/@fme_geometry_type = 'IFMEExtrusion'
      or $geom/@fme_geometry_type = 'IFMEBRepSolid'
      return number($geom/@fme_id)
    KIND = fme_composite_surface
    COERCED -> Deaggregator
    UNTOUCHED -> Deaggregator
Deaggregator
    ATTR_ACCUM_MODE = Merge List Attributes
    ATTR_CONFLICT_RES = Use List Attribute Values
    EXPLODE_INSTANCES = Yes
    GEOM_NAME_FIELD = _geometry_name
    LIST_ATTR_MODE_LOOKUP = LEAN
    MODE = Flatten All Levels
    SPLIT_COMPOSITES = No
    DEAGGREGATED -> Aggregator
Aggregator
    ACCUM_ATTRS_NAME = Merge Incoming Attributes
    AGGREGATE_TYPE = Homogeneous Collection (If Possible)
    GROUP_BY = fme_feature_type
    MODE = Geometry - Assemble One Level
    ORDERED = No
    SEP = ,
    AGGREGATE -> GeometryRefiner_3
GeometryRefiner_3
    -> Output (output)
Output (output)

FME custom transformer GetGrandParentID

Parameters:
- ATTR_TO_ENCODE =
- DEST_ATTR =

Bookmark: GetGrandParentID
Input (input)
    -> BinaryEncoder_3
BinaryEncoder_3
    ATTR_TO_ENCODE = $(ATTR_TO_ENCODE)
    DEST_ATTR = _parent_id
    ENCODING_TYPE = HEX
    -> VariableRetriever_5
VariableRetriever_5
    SCOPE = Global
    VALUE_ATTR = _gparent_id
    VARNAME = p@Value(_parent_id)
    -> BinaryDecoder
BinaryDecoder
    ATTR_ENCODING = utf-8
    ATTR_TO_DECODE = _gparent_id
    DEST_ATTR = $(DEST_ATTR)
    ENCODING_TYPE = HEX
    -> Output (output)
Output (output)

FME custom transformer CityGMLGeometrySetter

Parameters:
- GEOM =
- ROLE =

Bookmark: CityGMLGeometrySetter
INPUT (input)
    -> AttributeCreator
AttributeCreator
    ATTR_TABLE:
      SET_TO citygml_lod_name = $(GEOM)
      SET_TO citygml_feature_role = $(ROLE)
    -> GeometryPropertySetter
GeometryPropertySetter
    OVERWRITE_CHOICE = Yes
    REMOVE_ATTRIBUTE = No
    SETTYPE_PARAM = Traits From Attributes
    SRC_ATTRS = citygml_lod_name
    SET -> OUTPUT (output)
OUTPUT (output)
