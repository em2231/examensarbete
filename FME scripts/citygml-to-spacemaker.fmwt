FME workspace citygml-to-spacemaker.fmwt
Title: MULTI to MULTI

Parameters:
- DestDataset_GML =
- DestDataset_OBJ_3 =

Writers:
- OBJ_2: OBJ to $(DestDataset_OBJ_3)
- GML_1: GML to $(DestDataset_GML)

Note: Remove height
2DForcer
    2D -> Dissolver
Note: Select all polygons for export
Dissolver
    ACCUM_INPUT_ATTRS = Use Attributes From One Feature
    CLEANING_TOLERANCE = Automatic
    CONNECT_Z_MODE = First Wins
    DEAGGREGATE_INPUT = Yes
    AREA -> Roads_and_terrain (writer GML_1)
Roads_and_terrain (writer GML_1)
Existing buildings (writer OBJ_2)

Bookmark: Existing buildings, vegetation, roads and terrain to Spacemaker
Note: Existing buildings are converted to writer to export in OBJ
Note: Roads, terrain and vegetation are connected to 2D forcer
